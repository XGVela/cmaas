module xcf-cmaas-config {
    namespace "urn:rdns:org:xgvela:cmaas";

	prefix xgvela-cmaas;

        description "CMaaS service configuration.

                Copyright 2021 Mavenir

                Licensed under the Apache License, Version 2.0 (the \"License\");
                you may not use this file except in compliance with the License.
                You may obtain a copy of the License at

                http://www.apache.org/licenses/LICENSE-2.0

                Unless required by applicable law or agreed to in writing, software
                distributed under the License is distributed on an \"AS IS\" BASIS,
                WITHOUT WARRANTIES OR CONDITIONS OF ANY KIND, either express or implied.
                See the License for the specific language governing permissions and
                limitations under the License.";

	import ietf-inet-types { prefix inet; }

	import tailf-common { prefix tailf; }

	revision "2019-02-03" {
	    description "Initial revision";
	}
	container config {
		tailf:callpoint configUpdate {
			    tailf:transaction-hook subtree;
			}
	    leaf changeSetLease {
					type int64 {
                                                range 10..600;
                                               }
					mandatory true;
				}
		leaf logLevel {
					type enumeration {
                                                 enum TRACE;
                                                 enum FATAL;
                                                 enum ERROR;
                                                 enum WARN;
                                                 enum INFO;
                                                 enum DEBUG;
                                                 enum ALL;
                                             }
					mandatory true;
				}

	}
}
